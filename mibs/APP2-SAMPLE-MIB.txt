--
-- This SMIv2 module has been generated by smidump 0.4.8. Do not edit.
--

APP2-SAMPLE-MIB DEFINITIONS ::= BEGIN

IMPORTS
    customExample
        FROM CUSTOM-EXAMPLE-MIB
    OBJECT-GROUP
        FROM SNMPv2-CONF
    MODULE-IDENTITY, OBJECT-TYPE, TimeTicks
        FROM SNMPv2-SMI;

app2 MODULE-IDENTITY
    LAST-UPDATED "201701270000Z"
    ORGANIZATION
        "www.intraway.com"
    CONTACT-INFO
        "email:    nicolas.dascanio@intraway.com"
    DESCRIPTION
        "Example MIB objects for app2"
    REVISION    "201701270000Z"
    DESCRIPTION
        "First Revision"
    ::= { customExample 2 }


app2Scalars OBJECT IDENTIFIER
    ::= { app2 1 }

app2Name OBJECT-TYPE
    SYNTAX      OCTET STRING (SIZE(0..255))
    MAX-ACCESS  read-only
    STATUS      current
    DESCRIPTION
        "Component name"
    ::= { app2Scalars 1 }

app2Version OBJECT-TYPE
    SYNTAX      OCTET STRING (SIZE(0..32))
    MAX-ACCESS  read-only
    STATUS      current
    DESCRIPTION
        "Component version"
    ::= { app2Scalars 2 }

app2Status OBJECT-TYPE
    SYNTAX      INTEGER { down(0), up(1), disabled(2) }
    MAX-ACCESS  read-only
    STATUS      current
    DESCRIPTION
        "Component status"
    DEFVAL      { down }
    ::= { app2Scalars 3 }

app2Uptime OBJECT-TYPE
    SYNTAX      TimeTicks
    MAX-ACCESS  read-only
    STATUS      current
    DESCRIPTION
        "The time (in hundredths of a second) since the component was last re-initialized"
    ::= { app2Scalars 4 }

app2Tables OBJECT IDENTIFIER
    ::= { app2 2 }

app2MibConformance OBJECT IDENTIFIER
    ::= { app2 3 }

app2MibCompliances OBJECT IDENTIFIER
    ::= { app2MibConformance 1 }

app2MibGroups OBJECT IDENTIFIER
    ::= { app2MibConformance 2 }

app2ObjectsGroups OBJECT-GROUP
    OBJECTS     { app2Name, app2Version, app2Status, app2Uptime }
    STATUS      current
    DESCRIPTION
        "A collection of objects providing status and monitoring."
    ::= { app2MibGroups 1 }

END -- end of module APP2-SAMPLE-MIB.
