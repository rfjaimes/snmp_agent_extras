--
-- This SMIv2 module has been generated by smidump 0.4.8. Do not edit.
--

APP1-SAMPLE-MIB DEFINITIONS ::= BEGIN

IMPORTS
    customExample
        FROM CUSTOM-EXAMPLE-MIB
    OBJECT-GROUP
        FROM SNMPv2-CONF
    Counter32, Counter64, Gauge32, IpAddress, MODULE-IDENTITY,
    OBJECT-TYPE, TimeTicks
        FROM SNMPv2-SMI;

app1 MODULE-IDENTITY
    LAST-UPDATED "201701270000Z"
    ORGANIZATION
        "www.intraway.com"
    CONTACT-INFO
        "email:    nicolas.dascanio@intraway.com"
    DESCRIPTION
        "Example MIB objects for app1"
    REVISION    "201701270000Z"
    DESCRIPTION
        "First Revision"
    ::= { customExample 1 }


app1Scalars OBJECT IDENTIFIER
    ::= { app1 1 }

app1Name OBJECT-TYPE
    SYNTAX      OCTET STRING (SIZE(0..255))
    MAX-ACCESS  read-only
    STATUS      current
    DESCRIPTION
        "Component name"
    ::= { app1Scalars 1 }

app1Version OBJECT-TYPE
    SYNTAX      OCTET STRING (SIZE(0..32))
    MAX-ACCESS  read-only
    STATUS      current
    DESCRIPTION
        "Component version"
    ::= { app1Scalars 2 }

app1Status OBJECT-TYPE
    SYNTAX      INTEGER { down(0), up(1), disabled(2) }
    MAX-ACCESS  read-only
    STATUS      current
    DESCRIPTION
        "Component status"
    DEFVAL      { down }
    ::= { app1Scalars 3 }

app1Uptime OBJECT-TYPE
    SYNTAX      TimeTicks
    MAX-ACCESS  read-only
    STATUS      current
    DESCRIPTION
        "The time (in hundredths of a second) since the component was last re-initialized"
    ::= { app1Scalars 4 }

app1DummyAddress OBJECT-TYPE
    SYNTAX      IpAddress
    MAX-ACCESS  read-only
    STATUS      current
    DESCRIPTION
        "A dummy IP address"
    ::= { app1Scalars 5 }

app1SomeCounter OBJECT-TYPE
    SYNTAX      Counter32
    MAX-ACCESS  read-only
    STATUS      current
    DESCRIPTION
        "A dummy counter"
    ::= { app1Scalars 6 }

app1AnotherCounter OBJECT-TYPE
    SYNTAX      Gauge32
    MAX-ACCESS  read-only
    STATUS      current
    DESCRIPTION
        "Another dummy counter"
    ::= { app1Scalars 7 }

app1YetAnotherCounter OBJECT-TYPE
    SYNTAX      Counter64
    MAX-ACCESS  read-only
    STATUS      current
    DESCRIPTION
        "Yet another dummy counter"
    ::= { app1Scalars 8 }

app1Tables OBJECT IDENTIFIER
    ::= { app1 2 }

app1MibConformance OBJECT IDENTIFIER
    ::= { app1 3 }

app1MibCompliances OBJECT IDENTIFIER
    ::= { app1MibConformance 1 }

app1MibGroups OBJECT IDENTIFIER
    ::= { app1MibConformance 2 }

app1ObjectsGroups OBJECT-GROUP
    OBJECTS     { app1Name, app1Version, app1Status, app1Uptime,
                  app1DummyAddress, app1SomeCounter, app1AnotherCounter,
                  app1YetAnotherCounter }
    STATUS      current
    DESCRIPTION
        "A collection of objects providing status and monitoring."
    ::= { app1MibGroups 1 }

END -- end of module APP1-SAMPLE-MIB.
